module secondmodule {

  namespace "http://brewerslabng.mellon-collie.net/yang/integration-secondmodule";
  prefix "secondmodule";

  container second {
    description "This is not integrationtest.yang but secondmodule.";

    leaf second {
      type string;
    }
  }

  grouping group1 {
    list listgroup1 {
      key "key1 key2 key3";

      leaf key1 {
        type string;
      }
      leaf key2 {
        type string;
      }
      leaf key3 {
        type string;
      }
    }
  }
}
